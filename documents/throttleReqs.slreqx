# throttleReqs

## throttleReqs: References to throttleReqs.doc (Container)
Read-only references to Microsoft Word document.

### Input Scaling (Container)

#### inp_scl_1: Scaled data must be responsive t... (Functional)
Scaled data must be responsive to full range of input data.

#### inp_scl_2: Output range for each signal must be normalized. (Functional)

### PI Controller (Container)

#### pi_ctrl_1: Must implement standard proporti... (Functional)
Must implement standard proportional plus integral control algorithm.

#### pi_ctrl_2: Proportional and integral gains ... (Functional)
Proportional and integral gains should be adjustable.

#### pi_ctrl_3: Maximum value of integral state ... (Functional)
Maximum value of integral state cannot exceed 1 to prevent windup.

### PWM Conversion (Container)

#### pwm_1: Duty cycle must be proportional ... (Functional)
Duty cycle must be proportional to controller output, when in a valid range.

#### pwm_2: PWM torque should act in positiv... (Functional)
PWM torque should act in positive sense when controller output is positive or zero.

#### pwm_3: PWM torque should act in negativ... (Functional)
PWM torque should act in negative sense when controller output is negative.

#### pwm_4: Duty cycle must be in range from 0 to 1. (Functional)

#### pwm_5: Normal simulation and software-i... (Functional)
Normal simulation and software-in-the-loop simulation must produce identical outputs.

### Output Scaling (Container)

#### out_scl_1: Scaled data must be responsive t... (Functional)
Scaled data must be responsive to full range of input data.

#### out_scl_2: Output data must be scaled for d... (Functional)
Output data must be scaled for direct input to driver software.
